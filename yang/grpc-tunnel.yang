module grpc-tunnel {
    yang-version "1.1";

    // namespace
    namespace "urn:srl_sdk_apps/grpc-tunnel";
    prefix "srl_sdk_apps-grpc-tunnel";

    import srl_nokia-common {
        prefix srl-comm;
    }
    import srl_nokia-system {
        prefix srl-system;
    }
    import srl_nokia-network-instance {
        prefix srl-netinst;
    }
    import srl_nokia-tls {
        prefix srl-tls;
    }
    import srl_nokia-extensions {
        prefix srl-ext;
    }

    // description
    description
        "This module defines configuration and operational state data related to the SRLinux gRPC tunnel client.";

    // revision
    revision "2022-02-22" {
        description
          "grpc-tunnel 0.1.0";
    }
    
    grouping destination-state {
        leaf oper-state {
            type srl-comm:oper-state;
            config false;
            srl-ext:show-importance high;
            srl-ext:stream-mode on_change;
            description "Operational state of the destination";
        }
        leaf oper-state-down-reason {
            type string;
            config false;
            default "";
            // srl-ext:show-importance high;
            // srl-ext:stream-mode on_change;
            description "Reason the oper-state is DOWN";
        }
        list target {
            config false;
            key "id type";
            srl-ext:stream-mode on_change;
            leaf "id" {
                type string;
                description "gRPC tunnel target ID";
            }
            leaf type {
                type string;
                description "gRPC tunnel target type";
            }
            leaf oper-state {
                type srl-comm:oper-state;
                config false;
                srl-ext:show-importance high;
                description "Operational state of the target";
            }
            leaf oper-state-down-reason {
                type string;
                config false;
                default "";
                // srl-ext:show-importance high;
                description "Reason the oper-state is DOWN";
            }
        }
    } // destination-state grouping

    grouping grpc-tunnel-top {
        container grpc-tunnel {
            leaf admin-state {
                type srl-comm:admin-state;
                default "disable";
                srl-ext:show-importance high;
                description "Administrative state of the gRPC tunnel application";
            }
            leaf oper-state {
                type srl-comm:oper-state;
                config false;
                // srl-ext:show-importance high;
                srl-ext:stream-mode on_change;
                description "Operational state of the gRPC tunnel application";
            }
            list destination {
                description "list of gRPC tunnel destinations, i.e gRPC tunnel servers";
                key "name";
                max-elements 16;
                leaf name {
                    type string;
                    description "destination name";
                }
                leaf description {
                    type srl-comm:description;
                    description "destination description";
                }
                leaf address {
                    type srl-comm:ip-address;
                    description "destination address";
                }
                leaf port {
                    type srl-comm:port-number;
                    srl-ext:show-importance "high";
                    default "57401";
                    description "destination port number";
                }
                leaf network-instance {
                    type leafref {
                        path "/srl-netinst:network-instance/srl-netinst:name";
                    }
                    srl-ext:show-importance high;
                    default "mgmt";
                    description
                        "Reference to a configured network-instance used to establish the gRPC tunnel from.
                        This network-instance must already exist in the system.";
                }
                leaf no-tls {
                    description "when true the connection to this destination will be insecure";
                    type boolean;
                }
                leaf tls-profile {
                    type leafref {
                        path "/srl-system:system/srl-tls:tls/srl-tls:server-profile/srl-tls:name";
                    }
                    srl-ext:show-importance high;
                    description 
                        "NOT IMPLEMENTED: Reference to the TLS profile to use when initiating connections to this destination.
                        This TLS profile must already exist";
                }
            }
            list tunnel {
                description "gRPC tunnel(s)";
                key "name";
                max-elements 16;
                leaf name {
                    type string;
                    description "tunnel name";
                }
                leaf description {
                    type srl-comm:description;
                    description "tunnel description";
                }
                list destination {
                    key "name";
                    leaf "name" {
                        type leafref {
                            path "/srl-system:system/grpc-tunnel/destination/name";
                        }
                    }
                    max-elements 16;
                    description "reference to a created destination";
                    uses destination-state;
                }
                leaf admin-state {
                    type srl-comm:admin-state;
                    default "disable";
                    srl-ext:show-importance high;
                    description "Administrative state of the gRPC tunnel";
                }
                leaf oper-state {
                    type srl-comm:oper-state;
                    config false;
                    srl-ext:show-importance high;
                    description "Operational state of the gRPC tunnel";
                }
                leaf oper-state-down-reason {
                    type string;
                    config false;
                    default "";
                    // srl-ext:show-importance high;
                    description "Reason the oper-state is DOWN";
                }
                list target {
                    key "name";
                    max-elements 16;
                    leaf name {
                        type string {
                            length "1..256";
                        }
                        description "target local name";
                    }
                    container id {
                        description "target ID";
                        choice id {
                            default node-name;
                            case node-name {
                                leaf node-name {
                                    type empty;
                                }
                            }
                            case user-agent {
                                leaf user-agent {
                                    type empty;
                                }
                            }
                            case mac-address {
                                leaf mac-address {
                                    type empty;
                                }
                            }
                            case custom {
                                leaf custom {
                                    type string {
                                        length "1..max";
                                    }
                                }
                            }
                        }
                    }
                    container type {
                        description "target type";
                        choice type {
                            default grpc-server;
                            case grpc-server {
                                leaf grpc-server {
                                    type empty;
                                }
                            }
                            case ssh-server {
                                leaf ssh-server {
                                    type empty;
                                }
                            }
                            case custom {
                                leaf custom {
                                    type string {
                                       length "1..max";
                                    }
                                }
                            }
                        }
                    }
                    leaf local-address {
                        type string;
                        description "local address to dial for an established tunnel towards this target";
                    }
                } // list target
            } // list tunnel
        } // container grpc-tunnel
    } // grouping grpc-tunnel-top

    augment "/srl-system:system" {
        uses grpc-tunnel-top;
    }
}
